;
; Копирайт (С) 2019, ООО «Нанософт разработка». Все права защищены.
; 
; Данное программное обеспечение, все исключительные права на него, его
; документация и сопроводительные материалы принадлежат ООО «Нанософт разработка».
; Данное программное обеспечение может использоваться при разработке и входить
; в состав разработанных программных продуктов при соблюдении условий
; использования, оговоренных в «Лицензионном договоре присоединения
; на использование программы для ЭВМ «Платформа nanoCAD»».
; 
; Данное программное обеспечение защищено в соответствии с законодательством
; Российской Федерации об интеллектуальной собственности и международными
; правовыми актами.
; 
; Используя данное программное обеспечение,  его документацию и
; сопроводительные материалы вы соглашаетесь с условиями использования,
; указанными выше. 
;

; shows message box from .dcl file
(defun show-message-box (title msg)
  ; load DCL file
  (setq dcl (load_dialog "messagebox.dcl"))
  ; create new messagebox dialog
  (new_dialog "messagebox" dcl)
  ; set title and contents of messagebox
  (set_tile "dlg" title)
  (set_tile "message" msg)
  ; start dialog
  (setq res (start_dialog))
  ; after dialog exits, unload DCL file
  (unload_dialog dcl)
  res)

; message box command
(defun c:show-message-box ()
  (show-message-box "Message" "Hello!"))
