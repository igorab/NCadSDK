;
; Копирайт (С) 2019, ООО «Нанософт разработка». Все права защищены.
; 
; Данное программное обеспечение, все исключительные права на него, его
; документация и сопроводительные материалы принадлежат ООО «Нанософт разработка».
; Данное программное обеспечение может использоваться при разработке и входить
; в состав разработанных программных продуктов при соблюдении условий
; использования, оговоренных в «Лицензионном договоре присоединения
; на использование программы для ЭВМ «Платформа nanoCAD»».
; 
; Данное программное обеспечение защищено в соответствии с законодательством
; Российской Федерации об интеллектуальной собственности и международными
; правовыми актами.
; 
; Используя данное программное обеспечение,  его документацию и
; сопроводительные материалы вы соглашаетесь с условиями использования,
; указанными выше. 
;

; simply shows dialog from .dcl
(defun helloworld ()
  ; load DCL file
  (setq dcl (load_dialog "helloworld.dcl"))
  ; create new dialog by its name, in our case - "helloworld"
  (new_dialog "helloworld" dcl)
  ; now we can show dialog
  (start_dialog)
  ; after dialog exits, we must unload DCL file
  (unload_dialog dcl))

(defun c:helloworld ()
  (helloworld))
